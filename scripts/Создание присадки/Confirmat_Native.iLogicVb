' Native iLogic equivalent of 02_confirmat.py.
AddReference "System.Web.Extensions.dll"
AddReference "System.Drawing.dll"
AddReference "System.Windows.Forms.dll"
Imports Inventor
Imports System.Collections.Generic
Imports System.Diagnostics
Imports System.Globalization
Imports System.IO
Imports System.Text
Imports System.Text.RegularExpressions
Imports System.Web.Script.Serialization
Imports System.Windows.Forms

Public Class ThisRule
    Private Const ProjectRoot As String = "D:\Копия Google диска\02_Скрипты\01_Скрипты для работы\For Inventor\Присадка кодом Python"
    Private Const Prefix As String = "ConfirmatSketch"
    Private Const Tol As Double = 0.00001 ' см
    Private Const StepCm As Double = 3.2
    Private app As Inventor.Application
    Private part As PartDocument
    Private comp As PartComponentDefinition
    Private tg As TransientGeometry
    Private factory As TransientObjects
    Private log As StreamWriter
    Private config As Dictionary(Of String, Object)
    Private st As Dictionary(Of String, Object)
    Private nameMap As Dictionary(Of String, String)
    Private reserved As New Dictionary(Of String, HashSet(Of String))

    Private Const Workflow As String = "confirmat"

    Private Class SketchJob
        Public Sketch As PlanarSketch
        Public Edges As New List(Of SketchPoint)
        Public Centers As New List(Of SketchPoint)
    End Class

    Public Sub Main()
        app = ThisApplication
        reserved.Clear()
        Dim logPath As String = System.IO.Path.Combine(ProjectRoot, "02_confirmat_ilogic.log")
        Dim transaction As Inventor.Transaction = Nothing
        Dim previousScreen As Boolean = app.ScreenUpdating
        Using writer As New StreamWriter(logPath, False, New UTF8Encoding(False))
            log = writer
            Try
                WriteLog("02 Конфирмат Native. " & DateTime.Now.ToString("yyyy-MM-dd HH:mm:ss"))
                If app.ActiveDocument Is Nothing OrElse app.ActiveDocument.DocumentType <> DocumentTypeEnum.kPartDocumentObject Then
                    Throw New Exception("Откройте деталь .ipt и выберите плоские грани для присадки.")
                End If
                part = DirectCast(app.ActiveDocument, PartDocument)
                comp = part.ComponentDefinition
                tg = app.TransientGeometry
                factory = app.TransientObjects
                Dim faces As List(Of Face) = SelectedFaces()
                LoadConfig()
                Dim chosen() As String = ChooseParameters()
                If chosen Is Nothing Then Return
                Dim thickness As String = chosen(0), edgeOffset As String = chosen(1), countName As String = chosen(2)
                Dim countParameter As Inventor.Parameter = comp.Parameters.Item(countName)
                Dim count As Integer = ConfirmatCount(CDbl(countParameter.Value))
                If CDbl(comp.Parameters.Item(thickness).Value) <= 0 Then Throw New Exception("Толщина должна быть положительной.")
                Dim edgeValue As Double = CDbl(comp.Parameters.Item(edgeOffset).Value)
                If edgeValue < 0 Then Throw New Exception("Отступ от кромки не должен быть отрицательным.")
                ' Как в 02: глубина широкого участка равна выбранной толщине.
                For Each key As String In New String() {"outer_2pcs", "outer_3pcs"}
                    Dim values As Dictionary(Of String, Object) = Block(st, key)
                    values("depth") = thickness
                    st(key) = values
                Next
                Dim required As List(Of String) = RequiredParameters(thickness, edgeOffset)
                For Each name As String In required
                    Dim parameter As Inventor.Parameter = comp.Parameters.Item(name)
                Next
                Dim groups As New Dictionary(Of String, List(Of Face))
                For Each face As Face In faces
                    Dim key As String = PlaneKey(face)
                    If Not groups.ContainsKey(key) Then groups(key) = New List(Of Face)
                    groups(key).Add(face)
                Next
                transaction = app.TransactionManager.StartTransaction(part, "02 Конфирмат — iLogic Native")
                EnsureKeep(required)
                EnsureCountKeep(countParameter)
                Dim total As Stopwatch = Stopwatch.StartNew(), phase As Stopwatch = Stopwatch.StartNew()
                app.ScreenUpdating = False
                Dim jobs As New List(Of SketchJob)
                Dim faceIndex As Integer = 0, planeIndex As Integer = 0
                For Each group As List(Of Face) In groups.Values
                    planeIndex += 1
                    Dim plane As WorkPlane = comp.WorkPlanes.AddByPlaneAndOffset(group(0), thickness)
                    plane.Name = AvailableName(comp.WorkPlanes, Prefix & "_OffsetPlane_" & planeIndex.ToString(), "plane")
                    OptionalDisplay("Скрытие рабочей плоскости", Sub() plane.Visible = False)
                    Dim sketch As PlanarSketch = comp.Sketches.Add(plane)
                    sketch.Name = AvailableName(comp.Sketches, Prefix & "_" & planeIndex.ToString(), "sketch")
                    OptionalDisplay("Цвет эскиза", Sub() sketch.Color = factory.CreateColor(255, 220, 0))
                    Dim job As New SketchJob With {.Sketch = sketch}
                    sketch.DeferUpdates = True
                    Try
                        For Each face As Face In group
                            faceIndex += 1
                            BuildFace(job, face, edgeOffset, edgeValue, faceIndex)
                        Next
                    Finally
                        sketch.DeferUpdates = False
                    End Try
                    OptionalDisplay("Скрытие размеров", Sub() sketch.DimensionsVisible = False)
                    jobs.Add(job)
                Next
                LogStage("Все эскизы", phase)
                ' Исходные грани больше не используются после начала сверления.
                For Each job As SketchJob In jobs
                    Dim shareableSketch As Object = job.Sketch
                    Try
                        shareableSketch.Shared = True
                    Catch
                    End Try
                    Dim edgeFeatures As List(Of HoleFeature) = AddCounterbore(job.Edges, "outer_2pcs", "inner_2pcs", "Confirmat edges")
                    Dim centerFeatures As List(Of HoleFeature) = AddCounterbore(job.Centers, "outer_3pcs", "inner_3pcs", "Confirmat center")
                    For Each feature As HoleFeature In centerFeatures
                        ' Условие сохраняется в модели и реагирует на изменение количества.
                        feature.SetSuppressionCondition(countParameter, 60417, 2)
                    Next
                    OptionalDisplay("Скрытие эскиза", Sub() job.Sketch.Visible = False)
                Next
                LogStage("Все отверстия", phase)
                part.Update()
                LogStage("Обновление документа", phase)
                transaction.End()
                transaction = Nothing
                app.ScreenUpdating = previousScreen
                total.Stop()
                WriteLog("Общее время построения: " & Seconds(total) & "s")
                log.Flush()
                MessageBox.Show("Присадка конфирматов создана. Количество: " & count.ToString() & vbCrLf &
                                "Время построения: " & Seconds(total) & " с" & vbCrLf & "Журнал: " & logPath, "02 — iLogic Native")
            Catch ex As Exception
                WriteLog("ОШИБКА: " & ex.ToString())
                If transaction IsNot Nothing Then
                    Try
                        transaction.Abort()
                    Catch abortError As Exception
                        WriteLog("Откат: " & abortError.Message)
                    End Try
                End If
                log.Flush()
                MessageBox.Show(ex.Message & vbCrLf & "Подробности: " & logPath, "02 — ошибка", MessageBoxButtons.OK, MessageBoxIcon.Error)
            Finally
                app.ScreenUpdating = previousScreen
            End Try
        End Using
    End Sub

    Private Function SelectedFaces() As List(Of Face)
        Dim result As New List(Of Face), seen As New HashSet(Of String)
        For Each entity As Object In part.SelectSet
            If Not TypeOf entity Is Face Then Throw New Exception("Выберите только плоские грани детали.")
            Dim face As Face = DirectCast(entity, Face)
            If Not TypeOf face.Geometry Is Plane Then Throw New Exception("Для присадки требуются плоские грани.")
            Dim key As String = face.SurfaceBody.Name & ":" & face.TransientKey.ToString()
            If seen.Add(key) Then result.Add(face)
        Next
        If result.Count = 0 Then Throw New Exception("Выберите грани для присадки перед запуском правила.")
        Return result
    End Function

    Private Function ConfirmatCount(value As Double) As Integer
        If value = 2 OrElse value = 3 Then Return CInt(value)
        Throw New Exception("Параметр количества конфирматов должен быть равен 2 или 3.")
    End Function

    Private Sub BuildFace(job As SketchJob, face As Face, edgeOffset As String, edgeValue As Double, index As Integer)
        Dim sketch As PlanarSketch = job.Sketch
        Dim projected As New List(Of SketchLine)
        For Each edge As Edge In face.Edges
            Dim entity As Object = sketch.AddByProjectingEntity(edge)
            If TypeOf entity Is SketchLine Then projected.Add(DirectCast(entity, SketchLine))
        Next
        If projected.Count < 2 Then Throw New Exception("Недостаточно прямых рёбер для построения оси присадки.")
        ' Как в 02: ось между серединами двух самых коротких проекций.
        Dim lengths As New Dictionary(Of SketchLine, Double)
        For Each line As SketchLine In projected
            lengths(line) = LineLength(line)
        Next
        projected.Sort(Function(first As SketchLine, second As SketchLine) lengths(first).CompareTo(lengths(second)))
        Dim short1 As SketchLine = projected(0), short2 As SketchLine = projected(1)
        Dim a As Point2d = Midpoint(short1), b As Point2d = Midpoint(short2)
        Dim dx As Double = b.X - a.X, dy As Double = b.Y - a.Y
        Dim length As Double = Math.Sqrt(dx * dx + dy * dy)
        Dim span As Double = PointSpan(length, edgeValue)
        Dim ux As Double = dx / length, uy As Double = dy / length, nx As Double = -uy, ny As Double = ux
        Dim cx As Double = (a.X + b.X) / 2, cy As Double = (a.Y + b.Y) / 2
        Dim lines As SketchLines = sketch.SketchLines, points As SketchPoints = sketch.SketchPoints
        Dim g As GeometricConstraints = sketch.GeometricConstraints, dims As DimensionConstraints = sketch.DimensionConstraints
        Dim axis As SketchLine = ConstructionLine(lines, a, b)
        g.AddMidpoint(axis.StartSketchPoint, short1)
        g.AddMidpoint(axis.EndSketchPoint, short2)
        Dim symmetry As SketchLine = ConstructionLine(lines, P2(cx, cy), P2(cx + nx, cy + ny))
        g.AddMidpoint(symmetry.StartSketchPoint, axis)
        g.AddPerpendicular(symmetry, axis)
        Dim left As SketchPoint = points.Add(P2(cx - ux * span / 2, cy - uy * span / 2), False)
        Dim right As SketchPoint = points.Add(P2(cx + ux * span / 2, cy + uy * span / 2), False)
        Dim center As SketchPoint = points.Add(P2(cx, cy), False)
        g.AddCoincident(left, axis)
        g.AddCoincident(right, axis)
        g.AddSymmetry(left, right, symmetry)
        g.AddMidpoint(center, axis)
        Dim control As Object = dims.AddTwoPointDistance(axis.StartSketchPoint, axis.EndSketchPoint,
            DimensionOrientationEnum.kAlignedDim, P2(cx + nx * 4, cy + ny * 4), True)
        Dim name As String = AvailableName(comp.Parameters, "Long_edge_" & index.ToString(), "parameter")
        control.Parameter.Name = name
        Dim distance As Object = dims.AddTwoPointDistance(right, left, DimensionOrientationEnum.kAlignedDim,
                                                          P2(cx + nx * 2, cy + ny * 2), False)
        distance.Parameter.Name = AvailableName(comp.Parameters, "Расстояние_между_точками", "parameter")
        distance.Parameter.Expression = "floor((" & name & " - " & edgeOffset & " * 2) / 32 mm) * 32 mm"
        job.Edges.Add(left) : job.Edges.Add(right) : job.Centers.Add(center)
    End Sub

    Private Function Placement(points As List(Of SketchPoint)) As SketchHolePlacementDefinition
        Dim collection As ObjectCollection = factory.CreateObjectCollection()
        Dim seen As New HashSet(Of String)
        For Each point As SketchPoint In points
            Dim p As Point2d = point.Geometry
            If seen.Add(Rounded(p.X) & ":" & Rounded(p.Y)) Then
                point.HoleCenter = True
                collection.Add(point)
            End If
        Next
        Return comp.Features.HoleFeatures.CreateSketchPlacementDefinition(collection)
    End Function

    Private Function AddCounterbore(points As List(Of SketchPoint), outerKey As String, innerKey As String, defaultName As String) As List(Of HoleFeature)
        Dim outer As Dictionary(Of String, Object) = Block(st, outerKey), inner As Dictionary(Of String, Object) = Block(st, innerKey)
        Dim diameter As String = ResolveExpression(Text(inner, "diameter", "")), depth As String = ResolveExpression(Text(inner, "depth", ""))
        Dim cbDiameter As String = ResolveExpression(Text(outer, "diameter", "")), cbDepth As String = ResolveExpression(Text(outer, "depth", ""))
        Dim name As String = Text(outer, "feature_name", defaultName)
        Dim holes As HoleFeatures = comp.Features.HoleFeatures
        Dim result As New List(Of HoleFeature)
        Dim position As SketchHolePlacementDefinition = Placement(points)
        Dim feature As HoleFeature = Nothing
        Try
            feature = holes.AddCBoreByDistanceExtent(position, diameter, depth, PartFeatureExtentDirectionEnum.kPositiveExtentDirection, cbDiameter, cbDepth, True)
        Catch ex As Exception
            WriteLog("Counterbore API: " & ex.Message & "; создаются два соосных сверления.")
        End Try
        If feature IsNot Nothing Then
            result.Add(feature)
        Else
            ' Как в Python: резерв из двух операций с теми же центрами.
            result.Add(holes.AddDrilledByDistanceExtent(Placement(points), diameter, depth, PartFeatureExtentDirectionEnum.kPositiveExtentDirection, True))
            result.Add(holes.AddDrilledByDistanceExtent(Placement(points), cbDiameter, cbDepth, PartFeatureExtentDirectionEnum.kPositiveExtentDirection, True))
        End If
        For i As Integer = 0 To result.Count - 1
            ' Ошибки после создания не запускают повторное сверление: Main откатит транзакцию.
            result(i).Name = AvailableName(holes, name & If(i = 0, "", " outer"), "feature")
            Dim affected As ObjectCollection = factory.CreateObjectCollection()
            For Each body As SurfaceBody In comp.SurfaceBodies
                If body.IsSolid Then affected.Add(body)
            Next
            If affected.Count > 1 Then result(i).SetAffectedBodies(affected)
        Next
        WriteLog(name & "; центров: " & points.Count.ToString() & "; операций: " & result.Count.ToString())
        Return result
    End Function

    Private Function RequiredParameters(thickness As String, edgeOffset As String) As List(Of String)
        Dim result As New List(Of String) From {thickness, edgeOffset}
        For Each key As String In New String() {"outer_2pcs", "inner_2pcs", "outer_3pcs", "inner_3pcs"}
            For Each field As String In New String() {"diameter", "depth"}
                Dim expression As String = Text(Block(st, key), field, "")
                If expression = "" Then Throw New Exception("Нет настройки confirmat." & key & "." & field)
                Dim name As String = ResolveName(expression)
                If Regex.IsMatch(name, "^[^\W\d]\w*$") AndAlso Not result.Contains(name) Then result.Add(name)
            Next
        Next
        Return result
    End Function

    Private Sub EnsureCountKeep(source As Inventor.Parameter)
        Dim units As String = CStr(source.Units).Trim()
        If units.ToLowerInvariant() = "text" OrElse units.ToLowerInvariant() = "boolean" Then Throw New Exception("Количество должно быть числовым параметром.")
        Dim expression As String = CountKeepExpression(source.Name, units)
        Dim parameter As Inventor.Parameter = Nothing
        Try
            parameter = comp.Parameters.Item("Keep_Excel_Params_Unitless")
        Catch
        End Try
        If parameter Is Nothing Then
            comp.Parameters.UserParameters.AddByExpression("Keep_Excel_Params_Unitless", expression, UnitsTypeEnum.kUnitlessUnits)
        ElseIf Regex.Replace(parameter.Expression, "\s+", "") <> Regex.Replace(expression, "\s+", "") Then
            parameter.Expression = expression
        End If
    End Sub

    Private Function CountKeepExpression(name As String, units As String) As String
        If units = "" OrElse units.ToLowerInvariant() = "ul" Then Return name & " * 0"
        Return "(" & name & " / (1 " & units & ")) * 0"
    End Function

    Private Function ChooseParameters() As String()
        Dim names As New List(Of String)
        Dim loadNames As Action(Of Object) = Sub(collection As Object)
            For Each parameter As Inventor.Parameter In collection
                If Not names.Contains(parameter.Name) Then names.Add(parameter.Name)
            Next
            names.Sort(StringComparer.CurrentCulture)
        End Sub
        loadNames(comp.Parameters.UserParameters)
        Using dialog As New Form()
            dialog.Text = "02 Конфирмат — параметры присадки"
            dialog.Width = 900 : dialog.Height = 460
            dialog.Font = New System.Drawing.Font("Segoe UI", 10.0F)
            dialog.FormBorderStyle = FormBorderStyle.FixedDialog
            dialog.StartPosition = FormStartPosition.CenterScreen
            dialog.MaximizeBox = False : dialog.MinimizeBox = False : dialog.TopMost = True
            Dim labels() As String = {"Толщина материала:", "Отступ от кромки:", "Параметр количества (2 или 3):"}
            Dim filters() As String = {"толщина", "отступ", "конфирмат"}
            Dim defaults() As String = {"Толщина_каркаса_МДФ", "Минимальный_отступ_присадки_от_кромки_Каркас", "Количество_конфирматов"}
            Dim combos As New List(Of ComboBox)
            For i As Integer = 0 To 2
                Dim label As New Label With {.Left = 16, .Top = 16 + i * 86, .Width = 852, .Height = 26, .Text = labels(i)}
                Dim combo As New ComboBox With {.Left = 16, .Top = 46 + i * 86, .Width = 852, .DropDownWidth = 1000, .DropDownHeight = 280, .IntegralHeight = False, .DropDownStyle = ComboBoxStyle.DropDown}
                combos.Add(combo)
                dialog.Controls.Add(label) : dialog.Controls.Add(combo)
            Next
            Dim populate As Action = Sub()
                For i As Integer = 0 To 2
                    Dim current As String = combos(i).Text
                    combos(i).Items.Clear()
                    For Each name As String In names
                        Dim lower As String = name.ToLowerInvariant()
                        If lower.Contains(filters(i)) OrElse (i = 2 AndAlso lower.Contains("кол")) Then combos(i).Items.Add(name)
                    Next
                    If current <> "" Then
                        combos(i).Text = current
                    ElseIf combos(i).Items.Contains(defaults(i)) Then
                        combos(i).SelectedItem = defaults(i)
                    ElseIf combos(i).Items.Count > 0 Then
                        combos(i).SelectedIndex = 0
                    Else
                        combos(i).Text = defaults(i)
                    End If
                Next
            End Sub
            populate()
            Dim load As New Button With {.Left = 16, .Top = 320, .Width = 310, .Height = 36, .Text = "Загрузить параметры модели"}
            AddHandler load.Click, Sub(sender As Object, e As EventArgs)
                load.Enabled = False
                loadNames(comp.Parameters.ModelParameters)
                populate()
            End Sub
            Dim ok As New Button With {.Left = 640, .Top = 320, .Width = 100, .Height = 36, .Text = "OK", .DialogResult = DialogResult.OK}
            Dim cancel As New Button With {.Left = 756, .Top = 320, .Width = 112, .Height = 36, .Text = "Отмена", .DialogResult = DialogResult.Cancel}
            dialog.Controls.AddRange(New Control() {load, ok, cancel})
            dialog.AcceptButton = ok : dialog.CancelButton = cancel
            If dialog.ShowDialog() <> DialogResult.OK Then Return Nothing
            Dim result As New List(Of String)
            For Each combo As ComboBox In combos
                If combo.Text.Trim() = "" Then Throw New Exception("Выберите все три параметра.")
                result.Add(ResolveName(combo.Text.Trim()))
            Next
            Return result.ToArray()
        End Using
    End Function

    Private Sub LoadConfig()
        Dim serializer As New JavaScriptSerializer()
        config = New Dictionary(Of String, Object)
        Dim local As String = System.IO.Path.Combine(ProjectRoot, "settings.json")
        If System.IO.File.Exists(local) Then config = serializer.Deserialize(Of Dictionary(Of String, Object))(System.IO.File.ReadAllText(local, Encoding.UTF8))
        Dim library As String = System.IO.Path.GetFullPath(System.IO.Path.Combine(ProjectRoot, "..", "01_inventor_service", "service", "excel_parameters", "part_config.example.json"))
        If System.IO.File.Exists(library) Then
            Merge(config, serializer.Deserialize(Of Dictionary(Of String, Object))(System.IO.File.ReadAllText(library, Encoding.UTF8)))
        ElseIf config.Count = 0 Then
            Throw New Exception("Не найден файл настроек: " & library)
        End If
        nameMap = New Dictionary(Of String, String)
        If config.ContainsKey("linked_parameters") Then
            For Each item As Object In DirectCast(config("linked_parameters"), System.Collections.IEnumerable)
                Dim row As Dictionary(Of String, Object) = DirectCast(item, Dictionary(Of String, Object))
                Dim key As String = Text(row, "name", "")
                If key <> "" Then nameMap(key) = Text(row, "source_name", key)
            Next
        End If
        st = Block(config, Workflow)
        WriteLog("Настройки: " & If(System.IO.File.Exists(library), library, local))
    End Sub

    Private Sub Merge(target As Dictionary(Of String, Object), source As Dictionary(Of String, Object))
        For Each entry As KeyValuePair(Of String, Object) In source
            If target.ContainsKey(entry.Key) AndAlso TypeOf target(entry.Key) Is Dictionary(Of String, Object) AndAlso TypeOf entry.Value Is Dictionary(Of String, Object) Then
                Merge(DirectCast(target(entry.Key), Dictionary(Of String, Object)), DirectCast(entry.Value, Dictionary(Of String, Object)))
            Else
                target(entry.Key) = entry.Value
            End If
        Next
    End Sub

    Private Function ResolveName(name As String) As String
        Dim aliases As Dictionary(Of String, Object) = Block(config, "parameter_aliases")
        Dim resolved As String = Text(aliases, name, name)
        If nameMap.ContainsKey(resolved) Then Return nameMap(resolved)
        Return resolved
    End Function

    Private Function ResolveExpression(expression As String) As String
        Return Regex.Replace(expression, "[^\W\d]\w*", Function(m As Match) ResolveName(m.Value))
    End Function

    Private Sub EnsureKeep(names As List(Of String))
        Dim terms As New List(Of String)
        For Each name As String In names
            terms.Add(name & " * 0")
        Next
        Dim expression As String = String.Join(" + ", terms.ToArray())
        Dim parameter As Inventor.Parameter = Nothing
        Try
            parameter = comp.Parameters.Item("Keep_Excel_Params")
        Catch
        End Try
        If parameter Is Nothing Then
            comp.Parameters.UserParameters.AddByExpression("Keep_Excel_Params", expression, "mm")
        ElseIf Regex.Replace(parameter.Expression, "\s+", "") <> Regex.Replace(expression, "\s+", "") Then
            parameter.Expression = expression
        End If
    End Sub

    Private Function AvailableName(collection As Object, basis As String, category As String) As String
        If Not reserved.ContainsKey(category) Then reserved(category) = New HashSet(Of String)
        Dim index As Integer = 0
        Do
            Dim candidate As String = basis & If(index = 0, "", "_" & index.ToString())
            index += 1
            If reserved(category).Contains(candidate) Then Continue Do
            Try
                Dim existing As Object = collection.Item(candidate)
            Catch
                reserved(category).Add(candidate)
                Return candidate
            End Try
        Loop
    End Function

    Private Function PlaneKey(face As Face) As String
        Dim plane As Plane = DirectCast(face.Geometry, Plane)
        Dim n As UnitVector = plane.Normal, p As Inventor.Point = plane.RootPoint
        Dim sign As Double = 1
        For Each value As Double In New Double() {n.X, n.Y, n.Z}
            If Math.Abs(value) > 0.001 Then
                sign = If(value < 0, -1.0, 1.0)
                Exit For
            End If
        Next
        Dim distance As Double = (n.X * p.X + n.Y * p.Y + n.Z * p.Z) * sign
        Return Math.Round(n.X * sign, 3).ToString("F3", CultureInfo.InvariantCulture) & ":" &
               Math.Round(n.Y * sign, 3).ToString("F3", CultureInfo.InvariantCulture) & ":" &
               Math.Round(n.Z * sign, 3).ToString("F3", CultureInfo.InvariantCulture) & ":" &
               Math.Round(distance, 3).ToString("F3", CultureInfo.InvariantCulture)
    End Function

    Private Function PointSpan(length As Double, offset As Double) As Double
        Dim span As Double = Math.Floor((length - 2 * offset) / StepCm) * StepCm
        If offset < 0 OrElse span < 2 * StepCm Then Throw New Exception("Недостаточно места: расстояние крайних точек должно быть не меньше 64 мм.")
        Return span
    End Function

    Private Function ConstructionLine(lines As SketchLines, a As Point2d, b As Point2d) As SketchLine
        Dim result As SketchLine = lines.AddByTwoPoints(a, b)
        result.Construction = True
        Return result
    End Function

    Private Function LineLength(line As SketchLine) As Double
        Return line.StartSketchPoint.Geometry.DistanceTo(line.EndSketchPoint.Geometry)
    End Function

    Private Function Midpoint(line As SketchLine) As Point2d
        Dim a As Point2d = line.StartSketchPoint.Geometry, b As Point2d = line.EndSketchPoint.Geometry
        Return P2((a.X + b.X) / 2, (a.Y + b.Y) / 2)
    End Function

    Private Function P2(x As Double, y As Double) As Point2d
        Return tg.CreatePoint2d(x, y)
    End Function

    Private Function Direction(settings As Dictionary(Of String, Object)) As PartFeatureExtentDirectionEnum
        Dim value As String = Text(settings, "direction", "positive").ToLowerInvariant()
        If value = "negative" Then Return PartFeatureExtentDirectionEnum.kNegativeExtentDirection
        If value = "positive" Then Return PartFeatureExtentDirectionEnum.kPositiveExtentDirection
        Throw New Exception("Неизвестное направление отверстия: " & value)
    End Function

    Private Function Block(parent As Dictionary(Of String, Object), key As String) As Dictionary(Of String, Object)
        If parent.ContainsKey(key) AndAlso TypeOf parent(key) Is Dictionary(Of String, Object) Then Return DirectCast(parent(key), Dictionary(Of String, Object))
        Return New Dictionary(Of String, Object)
    End Function

    Private Function Text(parent As Dictionary(Of String, Object), key As String, fallback As String) As String
        If parent.ContainsKey(key) AndAlso parent(key) IsNot Nothing Then Return Convert.ToString(parent(key), CultureInfo.InvariantCulture)
        Return fallback
    End Function

    Private Function Rounded(value As Double) As String
        Return Math.Round(value, 6).ToString("F6", CultureInfo.InvariantCulture)
    End Function

    Private Sub IgnoreConstraint(action As Action)
        Try
            action()
        Catch ex As Exception
            WriteLog("  Зависимость пропущена: " & ex.Message)
        End Try
    End Sub

    Private Sub OptionalDisplay(label As String, action As Action)
        ' Как в Python: отказ оформления записать, но не отменять присадку.
        ' Этот обработчик не применяется к геометрии, размерам и отверстиям.
        Try
            action()
        Catch ex As Exception
            WriteLog("  Оформление пропущено (" & label & "): " & ex.Message)
        End Try
    End Sub

    Private Function Seconds(watch As Stopwatch) As String
        Return watch.Elapsed.TotalSeconds.ToString("F3", CultureInfo.InvariantCulture)
    End Function

    Private Sub LogStage(label As String, watch As Stopwatch)
        WriteLog(label & ": " & Seconds(watch) & "s")
        watch.Restart()
    End Sub

    Private Sub WriteLog(message As String)
        log.WriteLine(message)
        log.Flush()
    End Sub
End Class
