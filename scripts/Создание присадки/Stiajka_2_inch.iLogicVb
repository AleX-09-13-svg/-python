' Внешнее правило iLogic: присадка 05 непосредственно внутри Inventor 2023.
' Настройки и логика соответствуют 05_stiajka.py. Python не запускается.
AddReference "System.Web.Extensions.dll"
AddReference "System.Drawing.dll"
AddReference "System.Windows.Forms.dll"
Imports Inventor
Imports System.Collections.Generic
Imports System.Diagnostics
Imports System.Globalization
Imports System.IO
Imports System.Text
Imports System.Text.RegularExpressions
Imports System.Web.Script.Serialization
Imports System.Windows.Forms

Public Class ThisRule
    Private Const ProjectRoot As String = "D:\Копия Google диска\02_Скрипты\01_Скрипты для работы\For Inventor\Присадка кодом Python"
    Private Const Prefix As String = "DrillingSketch"
    Private Const Tol As Double = 0.00001 ' см
    Private Const StepCm As Double = 3.2
    Private app As Inventor.Application
    Private part As PartDocument
    Private comp As PartComponentDefinition
    Private tg As TransientGeometry
    Private factory As TransientObjects
    Private log As StreamWriter
    Private config As Dictionary(Of String, Object)
    Private st As Dictionary(Of String, Object)
    Private nameMap As Dictionary(Of String, String)
    Private bodies As New Dictionary(Of String, SurfaceBody)
    Private reserved As New Dictionary(Of String, HashSet(Of String))

    Private Class PairJob
        Public First As Face
        Public Second As Face
        Public Common As Edge
        Public Owner As String
        Public Neighbor As String
        Public Sketch1 As PlanarSketch
        Public Sketch2 As PlanarSketch
        Public Outer As New List(Of SketchPoint)
        Public Inner As New List(Of SketchPoint)
        Public Cups As New List(Of SketchPoint)
    End Class

    Private Class Projection
        Public Lines As New List(Of SketchLine)
        Public Reference As SketchLine
    End Class

    Private Class PostCreationException
        Inherits Exception
        Public Sub New(message As String, inner As Exception)
            MyBase.New(message, inner)
        End Sub
    End Class

    Public Sub Main()
        app = ThisApplication
        bodies.Clear()
        reserved.Clear()
        Dim logPath As String = System.IO.Path.Combine(ProjectRoot, "05_stiajka_ilogic.log")
        Dim transaction As Inventor.Transaction = Nothing
        Dim previousScreen As Boolean = app.ScreenUpdating
        Dim total As Stopwatch = Nothing
        Using writer As New StreamWriter(logPath, False, New UTF8Encoding(False))
            log = writer
            Try
                WriteLog("05 iLogic Native. " & DateTime.Now.ToString("yyyy-MM-dd HH:mm:ss"))
                If app.ActiveDocument Is Nothing OrElse app.ActiveDocument.DocumentType <> DocumentTypeEnum.kPartDocumentObject Then
                    Throw New Exception("Откройте деталь .ipt и выберите по две грани каждого тела.")
                End If
                part = DirectCast(app.ActiveDocument, PartDocument)
                comp = part.ComponentDefinition
                tg = app.TransientGeometry
                factory = app.TransientObjects
                Dim phase As Stopwatch = Stopwatch.StartNew()
                Dim jobs As List(Of PairJob) = SelectedPairs()
                LoadConfig()
                LogStage("Грани, общее ребро и настройки", phase)
                Dim edgeParam As String = ChooseOffset()
                If String.IsNullOrEmpty(edgeParam) Then
                    WriteLog("Отменено пользователем.")
                    Return
                End If
                phase.Restart()
                Dim offsetParam As String = SettingParameter("offset", "Стяжка_отступ")
                Dim required As List(Of String) = RequiredParameters(edgeParam)
                For Each name As String In required
                    Try
                        Dim parameter As Inventor.Parameter = comp.Parameters.Item(name)
                    Catch
                        Throw New Exception("В детали отсутствует параметр: " & name)
                    End Try
                Next
                Dim offsetValue As Double = CDbl(comp.Parameters.Item(offsetParam).Value)
                Dim edgeValue As Double = CDbl(comp.Parameters.Item(edgeParam).Value)
                If offsetValue <= 0 OrElse edgeValue < 0 Then Throw New Exception("Проверьте положительный отступ стяжки и отступ от кромки.")
                LogStage("Проверка параметров и чтение значений", phase)
                transaction = app.TransactionManager.StartTransaction(part, "05 Стяжка — iLogic Native")
                EnsureKeep(required)
                LogStage("Подготовка Keep_Excel_Params", phase)
                total = Stopwatch.StartNew()
                phase.Restart()
                app.ScreenUpdating = False
                Dim groups As New Dictionary(Of String, List(Of PairJob))
                For Each job As PairJob In jobs
                    Dim key As String = PlaneKey(job.First)
                    If Not groups.ContainsKey(key) Then groups(key) = New List(Of PairJob)
                    groups(key).Add(job)
                Next
                Dim index As Integer = 0
                Dim faceIndex As Integer = 0
                For Each group As List(Of PairJob) In groups.Values
                    index += 1
                    Dim sketch As PlanarSketch = NewSketch(group(0).First, index)
                    sketch.DeferUpdates = True
                    Try
                        For Each job As PairJob In group
                            faceIndex += 1
                            job.Sketch1 = sketch
                            BuildFirst(job, edgeParam, edgeValue, faceIndex)
                        Next
                    Finally
                        sketch.DeferUpdates = False
                    End Try
                    OptionalDisplay("Скрытие размеров " & sketch.Name, Sub() sketch.DimensionsVisible = False)
                Next
                LogStage("Первые эскизы", phase)
                For i As Integer = 0 To jobs.Count - 1
                    BuildSecond(jobs(i), edgeParam, edgeValue, offsetParam, offsetValue, i + 2)
                Next
                LogStage("Вторые эскизы", phase)
                ' До этого места отверстий нет: исходные ссылки на грани ещё действительны.
                For Each job As PairJob In jobs
                    job.Neighbor = FindNeighbor(job)
                Next
                LogStage("Поиск соседних тел", phase)
                For Each job As PairJob In jobs
                    Dim shareableSketch As Object = job.Sketch1
                    Try
                        shareableSketch.Shared = True
                    Catch
                    End Try
                    OptionalDisplay("Видимость первого эскиза", Sub() job.Sketch1.Visible = True)
                Next
                CreateBatches(jobs, "Otv_stijki_v_torec", False, False, "8 mm", "34 mm", "Stiajka outer 8x34")
                CreateBatches(jobs, "Otv_stijki_v_bokoviny", False, True, "5 mm", "13 mm", "Stiajka outer 5x13")
                CreateBatches(jobs, "shkant_v_plast", True, True, "8 mm", "10 mm", "Shkant 8x10")
                CreateBatches(jobs, "shkant_v_torets", True, False, "8 mm", "20 mm", "Shkant 8x20")
                Dim cup As Dictionary(Of String, Object) = Block(st, "Chashka stiajki")
                For Each job As PairJob In jobs
                    ' Как в Python: чашка использует stiajka.parameters.depth,
                    ' а не depth_parameter из блока Chashka stiajki.
                    AddHoles(job.Cups, SettingParameter("diameter", "Стяжка_D"),
                             SettingParameter("depth", "Стяжка_h"), Direction(cup),
                             Text(cup, "feature_name", "Stiajka cup"), job.Owner)
                    OptionalDisplay("Скрытие первого эскиза", Sub() job.Sketch1.Visible = False)
                    OptionalDisplay("Скрытие второго эскиза", Sub() job.Sketch2.Visible = False)
                Next
                LogStage("Все отверстия", phase)
                part.Update()
                LogStage("Обновление документа", phase)
                transaction.End()
                transaction = Nothing
                app.ScreenUpdating = previousScreen
                total.Stop()
                WriteLog("05: Общее время построения: " & Seconds(total) & "s")
                WriteLog("05: Готово. Пар граней: " & jobs.Count.ToString())
                log.Flush()
                MessageBox.Show("Присадка создана." & vbCrLf & "Время построения: " & Seconds(total) & " с" &
                                vbCrLf & "Журнал: " & logPath, "05 — iLogic Native")
            Catch ex As Exception
                WriteLog("ОШИБКА: " & ex.ToString())
                If transaction IsNot Nothing Then
                    Try
                        transaction.Abort()
                        WriteLog("Изменения этого запуска отменены.")
                    Catch rollback As Exception
                        WriteLog("Ошибка отмены: " & rollback.ToString())
                    End Try
                End If
                log.Flush()
                app.ScreenUpdating = previousScreen
                MessageBox.Show(ex.Message & vbCrLf & "Подробности: " & logPath, "05 — ошибка", MessageBoxButtons.OK, MessageBoxIcon.Error)
            Finally
                app.ScreenUpdating = previousScreen
            End Try
        End Using
    End Sub

    Private Function SelectedPairs() As List(Of PairJob)
        Dim groups As New Dictionary(Of String, List(Of Face))
        Dim seen As New HashSet(Of String)
        For Each entity As Object In part.SelectSet
            If Not TypeOf entity Is Face Then Continue For
            Dim face As Face = DirectCast(entity, Face)
            If Not TypeOf face.Geometry Is Plane Then Throw New Exception("Выбирайте только плоские грани.")
            Dim owner As String = face.SurfaceBody.Name
            Dim key As String = owner & ":" & face.TransientKey.ToString()
            If Not seen.Add(key) Then Continue For
            If Not groups.ContainsKey(owner) Then groups(owner) = New List(Of Face)
            groups(owner).Add(face)
            bodies(owner) = face.SurfaceBody
        Next
        If groups.Count = 0 Then Throw New Exception("Выберите узкую грань и пласть на каждом теле.")
        Dim result As New List(Of PairJob)
        For Each entry As KeyValuePair(Of String, List(Of Face)) In groups
            If entry.Value.Count <> 2 Then Throw New Exception("Тело '" & entry.Key & "': требуется ровно две выбранные грани.")
            Dim a As Face = entry.Value(0), b As Face = entry.Value(1)
            If a.Evaluator.Area > b.Evaluator.Area Then
                Dim swap As Face = a : a = b : b = swap
            End If
            Dim p As Plane = DirectCast(a.Geometry, Plane), q As Plane = DirectCast(b.Geometry, Plane)
            Dim n1 As UnitVector = p.Normal, n2 As UnitVector = q.Normal
            If NormalsCrossLengthSquared(n1.X, n1.Y, n1.Z, n2.X, n2.Y, n2.Z) < 0.00000001 Then
                Throw New Exception("Выбранные грани параллельны.")
            End If
            result.Add(New PairJob With {.First = a, .Second = b, .Common = SharedEdge(a, b), .Owner = entry.Key})
        Next
        WriteLog("Выбрано пар граней: " & result.Count.ToString())
        Return result
    End Function

    Private Function SharedEdge(first As Face, second As Face) As Edge
        Dim matches As New List(Of Edge)
        For Each a As Edge In first.Edges
            If CInt(a.GeometryType) <> 5122 AndAlso CInt(a.GeometryType) <> 5123 Then Continue For
            For Each b As Edge In second.Edges
                If SameEdge(a, b) Then
                    matches.Add(a)
                    Exit For
                End If
            Next
        Next
        If matches.Count <> 1 Then Throw New Exception("Требуется одно общее прямое ребро выбранных граней. Найдено: " & matches.Count.ToString())
        Return matches(0)
    End Function

    Private Function SameEdge(a As Edge, b As Edge) As Boolean
        If CInt(b.GeometryType) <> 5122 AndAlso CInt(b.GeometryType) <> 5123 Then Return False
        Dim a1 As Inventor.Point = a.StartVertex.Point, a2 As Inventor.Point = a.StopVertex.Point
        Dim b1 As Inventor.Point = b.StartVertex.Point, b2 As Inventor.Point = b.StopVertex.Point
        Return (a1.DistanceTo(b1) <= Tol AndAlso a2.DistanceTo(b2) <= Tol) OrElse
               (a1.DistanceTo(b2) <= Tol AndAlso a2.DistanceTo(b1) <= Tol)
    End Function

    Private Function NewSketch(face As Face, index As Integer) As PlanarSketch
        Dim sketch As PlanarSketch = comp.Sketches.Add(face)
        sketch.Name = AvailableName(comp.Sketches, Prefix & "_" & index.ToString(), "sketch")
        OptionalDisplay("Цвет эскиза " & sketch.Name, Sub() sketch.Color = factory.CreateColor(255, 220, 0))
        Return sketch
    End Function

    Private Function ProjectFace(sketch As PlanarSketch, face As Face, common As Edge) As Projection
        Dim result As New Projection
        For Each edge As Edge In face.Edges
            Dim projected As Object = sketch.AddByProjectingEntity(edge)
            If TypeOf projected Is SketchLine Then
                Dim line As SketchLine = DirectCast(projected, SketchLine)
                result.Lines.Add(line)
                If SameEdge(edge, common) Then result.Reference = line
            End If
        Next
        If result.Reference Is Nothing Then Throw New Exception("Не удалось спроецировать общее ребро.")
        Return result
    End Function

    Private Sub BuildFirst(job As PairJob, edgeParam As String, edgeValue As Double, index As Integer)
        Dim sk As PlanarSketch = job.Sketch1
        Dim projection As Projection = ProjectFace(sk, job.First, job.Common)
        Dim reference As SketchLine = projection.Reference
        Dim ends As List(Of SketchLine) = EndLines(reference, projection.Lines)
        Dim a As Point2d = Midpoint(ends(0)), b As Point2d = Midpoint(ends(1))
        Dim dx As Double = b.X - a.X, dy As Double = b.Y - a.Y
        Dim length As Double = Math.Sqrt(dx * dx + dy * dy)
        If length <= Tol Then Throw New Exception("Совпадают середины боковых рёбер.")
        Dim ux As Double = dx / length, uy As Double = dy / length
        Dim nx As Double = -uy, ny As Double = ux
        Dim cx As Double = (a.X + b.X) / 2, cy As Double = (a.Y + b.Y) / 2
        Dim lines As SketchLines = sk.SketchLines
        Dim g As GeometricConstraints = sk.GeometricConstraints
        Dim points As SketchPoints = sk.SketchPoints
        Dim dims As DimensionConstraints = sk.DimensionConstraints
        Dim axis As SketchLine = ConstructionLine(lines, a, b)
        IgnoreConstraint(Sub() g.AddMidpoint(axis.StartSketchPoint, ends(0)))
        IgnoreConstraint(Sub() g.AddMidpoint(axis.EndSketchPoint, ends(1)))
        Dim symmetry As SketchLine = ConstructionLine(lines, P2(cx - nx, cy - ny), P2(cx + nx, cy + ny))
        IgnoreConstraint(Sub() g.AddPerpendicular(axis, symmetry))
        IgnoreConstraint(Sub() g.AddMidpoint(symmetry.StartSketchPoint, axis))
        Dim referenceLength As Double = LineLength(reference)
        Dim span As Double = PointSpan(referenceLength, edgeValue), outer As Double = span / 2
        Dim left As SketchPoint = points.Add(P2(cx - ux * outer, cy - uy * outer), False)
        Dim right As SketchPoint = points.Add(P2(cx + ux * outer, cy + uy * outer), False)
        Dim center As SketchPoint = points.Add(P2(cx, cy), False)
        job.Outer.Add(left) : job.Outer.Add(right)
        IgnoreConstraint(Sub() g.AddCoincident(left, axis))
        IgnoreConstraint(Sub() g.AddCoincident(right, axis))
        IgnoreConstraint(Sub() g.AddCoincident(center, axis))
        IgnoreConstraint(Sub() g.AddCoincident(center, symmetry))
        IgnoreConstraint(Sub() g.AddSymmetry(left, right, symmetry))
        If span < StepCm * 3 Then
            job.Inner.Add(center)
        Else
            Dim inner As Double = outer - StepCm
            Dim li As SketchPoint = points.Add(P2(cx - ux * inner, cy - uy * inner), False)
            Dim ri As SketchPoint = points.Add(P2(cx + ux * inner, cy + uy * inner), False)
            job.Inner.Add(li) : job.Inner.Add(ri)
            IgnoreConstraint(Sub() g.AddCoincident(li, axis))
            IgnoreConstraint(Sub() g.AddCoincident(ri, axis))
            IgnoreConstraint(Sub() g.AddSymmetry(li, ri, symmetry))
            Dim inset As Object = dims.AddTwoPointDistance(left, li, DimensionOrientationEnum.kAlignedDim,
                                                          P2(cx - ux * (outer - 1.6) + nx * 2, cy - uy * (outer - 1.6) + ny * 2), False)
            inset.Parameter.Expression = "32 mm"
        End If
        ControlDimensions(dims, reference, left, right, P2(cx + nx * 4, cy + ny * 4),
                          P2(cx + nx * 2, cy + ny * 2), edgeParam, index)
    End Sub

    Private Sub BuildSecond(job As PairJob, edgeParam As String, edgeValue As Double,
                            offsetParam As String, offsetValue As Double, index As Integer)
        Dim sk As PlanarSketch = NewSketch(job.Second, index)
        job.Sketch2 = sk
        sk.DeferUpdates = True
        Try
            Dim projected As Projection = ProjectFace(sk, job.Second, job.Common)
            Dim reference As SketchLine = projected.Reference
            Dim a As Point2d = reference.StartSketchPoint.Geometry, b As Point2d = reference.EndSketchPoint.Geometry
            Dim length As Double = LineLength(reference)
            Dim ux As Double = (b.X - a.X) / length, uy As Double = (b.Y - a.Y) / length
            Dim nx As Double = -uy, ny As Double = ux
            Dim inside As Point2d = sk.ModelToSketchSpace(job.Second.PointOnFace)
            If (inside.X - a.X) * nx + (inside.Y - a.Y) * ny < 0 Then nx = -nx : ny = -ny
            Dim lines As SketchLines = sk.SketchLines
            Dim g As GeometricConstraints = sk.GeometricConstraints
            Dim points As SketchPoints = sk.SketchPoints
            Dim dims As DimensionConstraints = sk.DimensionConstraints
            Dim leftSide As SketchLine = Nothing, rightSide As SketchLine = Nothing
            For Each candidate As SketchLine In projected.Lines
                Dim p As Point2d = candidate.StartSketchPoint.Geometry, q As Point2d = candidate.EndSketchPoint.Geometry
                Dim t1 As Double = (p.X - a.X) * ux + (p.Y - a.Y) * uy
                Dim t2 As Double = (q.X - a.X) * ux + (q.Y - a.Y) * uy
                If Math.Abs(t1) < 0.0001 AndAlso Math.Abs(t2) < 0.0001 Then leftSide = candidate
                If Math.Abs(t1 - length) < 0.0001 AndAlso Math.Abs(t2 - length) < 0.0001 Then rightSide = candidate
            Next
            If leftSide Is Nothing Then leftSide = EndReference(lines, g, reference.StartSketchPoint, reference, nx, ny)
            If rightSide Is Nothing Then rightSide = EndReference(lines, g, reference.EndSketchPoint, reference, nx, ny)
            Dim cx As Double = (a.X + b.X) / 2 + nx * offsetValue
            Dim cy As Double = (a.Y + b.Y) / 2 + ny * offsetValue
            Dim axis As SketchLine = ConstructionLine(lines, P2(a.X + nx * offsetValue, a.Y + ny * offsetValue),
                                                      P2(b.X + nx * offsetValue, b.Y + ny * offsetValue))
            g.AddParallel(axis, reference)
            g.AddCoincident(axis.StartSketchPoint, leftSide)
            g.AddCoincident(axis.EndSketchPoint, rightSide)
            Dim anchor As SketchLine = ConstructionLine(lines, P2(cx - nx * offsetValue, cy - ny * offsetValue), P2(cx, cy))
            g.AddCoincident(anchor.StartSketchPoint, reference)
            g.AddMidpoint(anchor.EndSketchPoint, axis)
            g.AddPerpendicular(anchor, axis)
            Dim outer As Double = PointSpan(length, edgeValue) / 2
            Dim left As SketchPoint = points.Add(P2(cx - ux * outer, cy - uy * outer), False)
            Dim right As SketchPoint = points.Add(P2(cx + ux * outer, cy + uy * outer), False)
            job.Cups.Add(left) : job.Cups.Add(right)
            IgnoreConstraint(Sub() g.AddCoincident(left, axis))
            IgnoreConstraint(Sub() g.AddCoincident(right, axis))
            IgnoreConstraint(Sub() g.AddSymmetry(left, right, anchor))
            ControlDimensions(dims, reference, left, right, P2(cx + nx * 4, cy + ny * 4),
                              P2(cx + nx * 2, cy + ny * 2), edgeParam, index)
            Dim offsetDim As Object = dims.AddTwoPointDistance(anchor.StartSketchPoint, anchor.EndSketchPoint,
                DimensionOrientationEnum.kAlignedDim, P2(cx - nx * offsetValue / 2 + ux * 2, cy - ny * offsetValue / 2 + uy * 2), False)
            offsetDim.Parameter.Expression = offsetParam
        Finally
            sk.DeferUpdates = False
        End Try
        OptionalDisplay("Скрытие размеров " & sk.Name, Sub() sk.DimensionsVisible = False)
    End Sub

    Private Sub ControlDimensions(dims As DimensionConstraints, reference As SketchLine, left As SketchPoint,
                                  right As SketchPoint, controlText As Point2d, spanText As Point2d,
                                  edgeParam As String, index As Integer)
        Dim control As Object = dims.AddTwoPointDistance(reference.StartSketchPoint, reference.EndSketchPoint,
                                                         DimensionOrientationEnum.kAlignedDim, controlText, True)
        Dim name As String = AvailableName(comp.Parameters, "Long_edge_" & index.ToString(), "parameter")
        control.Parameter.Name = name
        Dim span As Object = dims.AddTwoPointDistance(right, left, DimensionOrientationEnum.kAlignedDim, spanText, False)
        span.Parameter.Name = AvailableName(comp.Parameters, "Расстояние_между_точками", "parameter")
        span.Parameter.Expression = "floor((" & name & " - " & edgeParam & " * 2) / 32 mm) * 32 mm"
    End Sub

    Private Function EndReference(lines As SketchLines, g As GeometricConstraints, point As SketchPoint,
                                  reference As SketchLine, nx As Double, ny As Double) As SketchLine
        Dim p As Point2d = point.Geometry
        Dim result As SketchLine = ConstructionLine(lines, p, P2(p.X + nx, p.Y + ny))
        g.AddCoincident(result.StartSketchPoint, point)
        g.AddPerpendicular(result, reference)
        Return result
    End Function

    Private Function FindNeighbor(job As PairJob) As String
        Dim samples As New List(Of Inventor.Point)
        For Each p As SketchPoint In job.Outer
            samples.Add(job.Sketch1.SketchToModelSpace(p.Geometry))
        Next
        For Each p As SketchPoint In job.Inner
            samples.Add(job.Sketch1.SketchToModelSpace(p.Geometry))
        Next
        Dim found As New HashSet(Of String)
        Dim filters() As SelectionFilterEnum = {SelectionFilterEnum.kPartFaceFilter}
        For Each sample As Inventor.Point In samples
            Dim entities As ObjectsEnumerator = Nothing
            Try
                entities = comp.FindUsingPoint(sample, filters, Tol, False)
            Catch ex As System.Runtime.InteropServices.COMException
                WriteLog("Поиск по точке: " & ex.Message)
                Continue For
            End Try
            If entities Is Nothing Then Continue For
            For Each entity As Object In entities
                If Not TypeOf entity Is Face Then Continue For
                Dim face As Face = DirectCast(entity, Face)
                Dim body As SurfaceBody = face.SurfaceBody
                Dim name As String = body.Name
                If name = job.Owner OrElse found.Contains(name) OrElse Not body.IsSolid Then Continue For
                If Not SamePlane(job.First, face) Then Continue For
                Dim contains As Boolean = True
                For Each p As Inventor.Point In samples
                    If face.GetClosestPointTo(p).DistanceTo(p) > Tol Then contains = False : Exit For
                Next
                If contains Then found.Add(name) : bodies(name) = body
            Next
            If found.Count > 0 Then Exit For
        Next
        If found.Count <> 1 Then Throw New Exception("Тело '" & job.Owner & "': требуется один сосед с совпадающей гранью. Найдено: " & found.Count.ToString())
        Dim result As String = Nothing
        For Each name As String In found
            result = name
        Next
        WriteLog("Тело выбранной грани: " & job.Owner & "; соседнее тело: " & result)
        Return result
    End Function

    Private Sub CreateBatches(jobs As List(Of PairJob), key As String, inner As Boolean, neighbor As Boolean,
                             defaultD As String, defaultH As String, defaultName As String)
        Dim sets As New Dictionary(Of String, List(Of SketchPoint))
        Dim owners As New Dictionary(Of String, String)
        Dim groupedJobs As New Dictionary(Of String, List(Of PairJob))
        For Each job As PairJob In jobs
            Dim bodyName As String = If(neighbor, job.Neighbor, job.Owner)
            Dim groupKey As String = bodyName & vbTab & job.Sketch1.Name
            If Not sets.ContainsKey(groupKey) Then
                sets(groupKey) = New List(Of SketchPoint)
                groupedJobs(groupKey) = New List(Of PairJob)
            End If
            sets(groupKey).AddRange(If(inner, job.Inner, job.Outer))
            groupedJobs(groupKey).Add(job)
            owners(groupKey) = bodyName
        Next
        Dim settings As Dictionary(Of String, Object) = Block(st, key)
        For Each entry As KeyValuePair(Of String, List(Of SketchPoint)) In sets
            Try
                AddHoles(entry.Value, ResolveExpression(Text(settings, "diameter", defaultD)),
                         ResolveExpression(Text(settings, "depth", defaultH)), Direction(settings),
                         Text(settings, "feature_name", defaultName), owners(entry.Key))
            Catch ex As PostCreationException
                Throw
            Catch ex As Exception
                If groupedJobs(entry.Key).Count = 1 Then Throw
                WriteLog("Пакет " & key & " отклонён, обработка по парам: " & ex.Message)
                For Each job As PairJob In groupedJobs(entry.Key)
                    AddHoles(If(inner, job.Inner, job.Outer), ResolveExpression(Text(settings, "diameter", defaultD)),
                             ResolveExpression(Text(settings, "depth", defaultH)), Direction(settings),
                             Text(settings, "feature_name", defaultName), owners(entry.Key))
                Next
            End Try
        Next
    End Sub

    Private Sub AddHoles(points As List(Of SketchPoint), diameter As String, depth As String,
                         direction As PartFeatureExtentDirectionEnum, name As String, bodyName As String)
        Dim watch As Stopwatch = Stopwatch.StartNew()
        Dim centers As ObjectCollection = factory.CreateObjectCollection()
        Dim seen As New HashSet(Of String)
        For Each p As SketchPoint In points
            Dim key As String = Rounded(p.Geometry.X) & ":" & Rounded(p.Geometry.Y)
            If seen.Add(key) Then
                p.HoleCenter = True
                centers.Add(p)
            End If
        Next
        Dim holes As HoleFeatures = comp.Features.HoleFeatures
        Dim placement As SketchHolePlacementDefinition = holes.CreateSketchPlacementDefinition(centers)
        Dim feature As HoleFeature = holes.AddDrilledByDistanceExtent(placement, diameter, depth, direction, True)
        Try
            feature.Name = AvailableName(holes, name, "feature")
            Dim affected As ObjectCollection = factory.CreateObjectCollection()
            affected.Add(CurrentBody(bodyName))
            feature.SetAffectedBodies(affected)
        Catch ex As Exception
            ' Не повторять сверление, если сама операция уже создана.
            ' Main отменит всю транзакцию вместе с этой операцией.
            Throw New PostCreationException("Не удалось завершить операцию '" & name & "' для тела '" & bodyName & "'.", ex)
        End Try
        WriteLog("  " & name & "; тело: " & bodyName & "; центров: " & centers.Count.ToString() & "; " & Seconds(watch) & "s")
    End Sub

    Private Function CurrentBody(name As String) As SurfaceBody
        If bodies.ContainsKey(name) Then
            Try
                If bodies(name).Name = name Then Return bodies(name)
            Catch
            End Try
        End If
        For Each body As SurfaceBody In comp.SurfaceBodies
            If body.Name = name Then bodies(name) = body : Return body
        Next
        Throw New Exception("Целевое тело не найдено: " & name)
    End Function

    Private Sub LoadConfig()
        Dim serializer As New JavaScriptSerializer()
        config = New Dictionary(Of String, Object)
        Dim local As String = System.IO.Path.Combine(ProjectRoot, "settings.json")
        If System.IO.File.Exists(local) Then config = serializer.Deserialize(Of Dictionary(Of String, Object))(System.IO.File.ReadAllText(local, Encoding.UTF8))
        Dim library As String = System.IO.Path.GetFullPath(System.IO.Path.Combine(ProjectRoot, "..", "01_inventor_service", "service", "excel_parameters", "part_config.example.json"))
        If System.IO.File.Exists(library) Then
            Merge(config, serializer.Deserialize(Of Dictionary(Of String, Object))(System.IO.File.ReadAllText(library, Encoding.UTF8)))
        ElseIf config.Count = 0 Then
            Throw New Exception("Не найден файл настроек: " & library)
        End If
        nameMap = New Dictionary(Of String, String)
        If config.ContainsKey("linked_parameters") Then
            For Each item As Object In DirectCast(config("linked_parameters"), System.Collections.IEnumerable)
                Dim row As Dictionary(Of String, Object) = DirectCast(item, Dictionary(Of String, Object))
                Dim key As String = Text(row, "name", "")
                If key <> "" Then nameMap(key) = Text(row, "source_name", key)
            Next
        End If
        st = Block(config, "stiajka")
        WriteLog("Настройки: " & If(System.IO.File.Exists(library), library, local))
    End Sub

    Private Sub Merge(target As Dictionary(Of String, Object), source As Dictionary(Of String, Object))
        For Each entry As KeyValuePair(Of String, Object) In source
            If target.ContainsKey(entry.Key) AndAlso TypeOf target(entry.Key) Is Dictionary(Of String, Object) AndAlso TypeOf entry.Value Is Dictionary(Of String, Object) Then
                Merge(DirectCast(target(entry.Key), Dictionary(Of String, Object)), DirectCast(entry.Value, Dictionary(Of String, Object)))
            Else
                target(entry.Key) = entry.Value
            End If
        Next
    End Sub

    Private Function ResolveName(name As String) As String
        Dim aliases As Dictionary(Of String, Object) = Block(config, "parameter_aliases")
        Dim resolved As String = Text(aliases, name, name)
        If nameMap.ContainsKey(resolved) Then Return nameMap(resolved)
        Return resolved
    End Function

    Private Function ResolveExpression(expression As String) As String
        Return Regex.Replace(expression, "[^\W\d]\w*", Function(m As Match) ResolveName(m.Value))
    End Function

    Private Function SettingParameter(key As String, fallback As String) As String
        Return ResolveName(Text(Block(st, "parameters"), key, fallback))
    End Function

    Private Function RequiredParameters(edgeParam As String) As List(Of String)
        Dim result As New List(Of String)
        result.Add(edgeParam)
        result.Add(SettingParameter("offset", "Стяжка_отступ"))
        result.Add(SettingParameter("diameter", "Стяжка_D"))
        result.Add(SettingParameter("depth", "Стяжка_h"))
        For Each key As String In New String() {"Otv_stijki_v_torec", "Otv_stijki_v_bokoviny", "shkant_v_plast", "shkant_v_torets"}
            Dim settings As Dictionary(Of String, Object) = Block(st, key)
            For Each field As String In New String() {"diameter", "depth"}
                Dim name As String = ResolveName(Text(settings, field, ""))
                If Regex.IsMatch(name, "^[^\W\d]\w*$") AndAlso Not result.Contains(name) Then result.Add(name)
            Next
        Next
        Dim cup As Dictionary(Of String, Object) = Block(st, "Chashka stiajki")
        For Each field As String In New String() {"diameter_parameter", "depth_parameter"}
            Dim name As String = ResolveName(Text(cup, field, ""))
            If name <> "" AndAlso Not result.Contains(name) Then result.Add(name)
        Next
        Dim unique As New List(Of String)
        For Each name As String In result
            If Not unique.Contains(name) Then unique.Add(name)
        Next
        Return unique
    End Function

    Private Sub EnsureKeep(names As List(Of String))
        Dim terms As New List(Of String)
        For Each name As String In names
            terms.Add(name & " * 0")
        Next
        Dim expression As String = String.Join(" + ", terms.ToArray())
        Dim parameter As Inventor.Parameter = Nothing
        Try
            parameter = comp.Parameters.Item("Keep_Excel_Params")
        Catch
        End Try
        If parameter Is Nothing Then
            comp.Parameters.UserParameters.AddByExpression("Keep_Excel_Params", expression, "mm")
        ElseIf Regex.Replace(parameter.Expression, "\s+", "") <> Regex.Replace(expression, "\s+", "") Then
            parameter.Expression = expression
        End If
    End Sub

    Private Function ChooseOffset() As String
        Dim options As New List(Of String)
        Dim loadNames As Action(Of Object) = Sub(parameters As Object)
            For Each parameter As Inventor.Parameter In parameters
                If parameter.Name.IndexOf("отступ", StringComparison.OrdinalIgnoreCase) >= 0 AndAlso Not options.Contains(parameter.Name) Then options.Add(parameter.Name)
            Next
            options.Sort(StringComparer.CurrentCulture)
        End Sub
        Dim watch As Stopwatch = Stopwatch.StartNew()
        loadNames(comp.Parameters.UserParameters)
        WriteLog("Чтение пользовательских параметров: " & Seconds(watch) & "s")
        Using dialog As New Form()
            dialog.Text = "05 iLogic — параметр отступа"
            dialog.Width = 900 : dialog.Height = 460
            dialog.Font = New System.Drawing.Font("Segoe UI", 10.0F)
            dialog.FormBorderStyle = FormBorderStyle.FixedDialog
            dialog.StartPosition = FormStartPosition.CenterScreen
            dialog.MaximizeBox = False : dialog.MinimizeBox = False
            dialog.TopMost = True
            Dim label As New Label With {.Left = 16, .Top = 16, .Width = 852, .Height = 26, .Text = "Параметр минимального отступа присадки от кромки:"}
            Dim combo As New ComboBox With {.Left = 16, .Top = 52, .Width = 852, .DropDownWidth = 1000, .DropDownHeight = 320, .IntegralHeight = False, .DropDownStyle = ComboBoxStyle.DropDownList}
            combo.Items.AddRange(options.ToArray())
            If combo.Items.Count > 0 Then combo.SelectedIndex = 0
            Dim preferred As String = "Минимальный_отступ_присадки_от_кромки_Каркас"
            If combo.Items.Contains(preferred) Then combo.SelectedItem = preferred
            Dim load As New Button With {.Left = 16, .Top = 115, .Width = 310, .Height = 36, .Text = "Загрузить параметры модели"}
            AddHandler load.Click, Sub(sender As Object, e As EventArgs)
                Dim current As String = CStr(combo.SelectedItem)
                Dim timer As Stopwatch = Stopwatch.StartNew()
                loadNames(comp.Parameters.ModelParameters)
                combo.Items.Clear() : combo.Items.AddRange(options.ToArray())
                If current IsNot Nothing AndAlso combo.Items.Contains(current) Then
                    combo.SelectedItem = current
                ElseIf combo.Items.Count > 0 Then
                    combo.SelectedIndex = 0
                End If
                load.Enabled = False
                WriteLog("Чтение параметров модели: " & Seconds(timer) & "s")
            End Sub
            Dim ok As New Button With {.Left = 640, .Top = 115, .Width = 100, .Height = 36, .Text = "OK", .DialogResult = DialogResult.OK}
            Dim cancel As New Button With {.Left = 756, .Top = 115, .Width = 112, .Height = 36, .Text = "Отмена", .DialogResult = DialogResult.Cancel}
            dialog.Controls.AddRange(New Control() {label, combo, load, ok, cancel})
            dialog.AcceptButton = ok : dialog.CancelButton = cancel
            If dialog.ShowDialog() <> DialogResult.OK OrElse combo.SelectedItem Is Nothing Then Return Nothing
            Return CStr(combo.SelectedItem)
        End Using
    End Function

    Private Function AvailableName(collection As Object, basis As String, category As String) As String
        If Not reserved.ContainsKey(category) Then reserved(category) = New HashSet(Of String)
        Dim index As Integer = 0
        Do
            Dim candidate As String = basis & If(index = 0, "", "_" & index.ToString())
            index += 1
            If reserved(category).Contains(candidate) Then Continue Do
            Try
                Dim existing As Object = collection.Item(candidate)
            Catch
                reserved(category).Add(candidate)
                Return candidate
            End Try
        Loop
    End Function

    Private Function EndLines(reference As SketchLine, lines As List(Of SketchLine)) As List(Of SketchLine)
        Dim result As New List(Of SketchLine)
        Dim a As Point2d = reference.StartSketchPoint.Geometry, b As Point2d = reference.EndSketchPoint.Geometry
        For Each endpoint As Point2d In New Point2d() {a, b}
            Dim candidates As New List(Of SketchLine)
            For Each line As SketchLine In lines
                Dim p As Point2d = line.StartSketchPoint.Geometry, q As Point2d = line.EndSketchPoint.Geometry
                Dim cross As Double = (q.X - p.X) * (b.Y - a.Y) - (q.Y - p.Y) * (b.X - a.X)
                If Math.Abs(cross) <= Tol Then Continue For
                If p.DistanceTo(endpoint) <= Tol OrElse q.DistanceTo(endpoint) <= Tol Then candidates.Add(line)
            Next
            If candidates.Count <> 1 Then Throw New Exception("Неоднозначные боковые рёбра у конца общего ребра.")
            result.Add(candidates(0))
        Next
        Return result
    End Function

    Private Function PlaneKey(face As Face) As String
        Dim plane As Plane = DirectCast(face.Geometry, Plane)
        Dim n As UnitVector = plane.Normal, p As Inventor.Point = plane.RootPoint
        Dim sign As Double = 1
        For Each value As Double In New Double() {n.X, n.Y, n.Z}
            If Math.Abs(value) > 0.001 Then
                sign = If(value < 0, -1.0, 1.0)
                Exit For
            End If
        Next
        Dim distance As Double = (n.X * p.X + n.Y * p.Y + n.Z * p.Z) * sign
        Return Math.Round(n.X * sign, 3).ToString("F3", CultureInfo.InvariantCulture) & ":" &
               Math.Round(n.Y * sign, 3).ToString("F3", CultureInfo.InvariantCulture) & ":" &
               Math.Round(n.Z * sign, 3).ToString("F3", CultureInfo.InvariantCulture) & ":" &
               Math.Round(distance, 3).ToString("F3", CultureInfo.InvariantCulture)
    End Function

    Private Function SamePlane(a As Face, b As Face) As Boolean
        Dim p As Plane = TryCast(a.Geometry, Plane), q As Plane = TryCast(b.Geometry, Plane)
        If p Is Nothing OrElse q Is Nothing Then Return False
        Dim n As UnitVector = p.Normal, m As UnitVector = q.Normal
        Dim dot As Double = n.X * m.X + n.Y * m.Y + n.Z * m.Z
        Dim x As Inventor.Point = p.RootPoint, y As Inventor.Point = q.RootPoint
        Return Math.Abs(Math.Abs(dot) - 1) <= Tol AndAlso
               Math.Abs((y.X - x.X) * n.X + (y.Y - x.Y) * n.Y + (y.Z - x.Z) * n.Z) <= Tol
    End Function

    Private Function NormalsCrossLengthSquared(ax As Double, ay As Double, az As Double,
                                               bx As Double, by As Double, bz As Double) As Double
        ' Числовой расчёт не требует приведения результата UnitVector.CrossProduct
        ' к несовместимому COM-интерфейсу Inventor.Vector.
        Dim x As Double = ay * bz - az * by
        Dim y As Double = az * bx - ax * bz
        Dim z As Double = ax * by - ay * bx
        Return x * x + y * y + z * z
    End Function

    Private Function PointSpan(length As Double, offset As Double) As Double
        Dim span As Double = Math.Floor((length - 2 * offset) / StepCm) * StepCm
        If offset < 0 OrElse span < 2 * StepCm Then Throw New Exception("Недостаточно места: расстояние крайних точек должно быть не меньше 64 мм.")
        Return span
    End Function

    Private Function ConstructionLine(lines As SketchLines, a As Point2d, b As Point2d) As SketchLine
        Dim result As SketchLine = lines.AddByTwoPoints(a, b)
        result.Construction = True
        Return result
    End Function

    Private Function LineLength(line As SketchLine) As Double
        Return line.StartSketchPoint.Geometry.DistanceTo(line.EndSketchPoint.Geometry)
    End Function

    Private Function Midpoint(line As SketchLine) As Point2d
        Dim a As Point2d = line.StartSketchPoint.Geometry, b As Point2d = line.EndSketchPoint.Geometry
        Return P2((a.X + b.X) / 2, (a.Y + b.Y) / 2)
    End Function

    Private Function P2(x As Double, y As Double) As Point2d
        Return tg.CreatePoint2d(x, y)
    End Function

    Private Function Direction(settings As Dictionary(Of String, Object)) As PartFeatureExtentDirectionEnum
        Dim value As String = Text(settings, "direction", "positive").ToLowerInvariant()
        If value = "negative" Then Return PartFeatureExtentDirectionEnum.kNegativeExtentDirection
        If value = "positive" Then Return PartFeatureExtentDirectionEnum.kPositiveExtentDirection
        Throw New Exception("Неизвестное направление отверстия: " & value)
    End Function

    Private Function Block(parent As Dictionary(Of String, Object), key As String) As Dictionary(Of String, Object)
        If parent.ContainsKey(key) AndAlso TypeOf parent(key) Is Dictionary(Of String, Object) Then Return DirectCast(parent(key), Dictionary(Of String, Object))
        Return New Dictionary(Of String, Object)
    End Function

    Private Function Text(parent As Dictionary(Of String, Object), key As String, fallback As String) As String
        If parent.ContainsKey(key) AndAlso parent(key) IsNot Nothing Then Return Convert.ToString(parent(key), CultureInfo.InvariantCulture)
        Return fallback
    End Function

    Private Function Rounded(value As Double) As String
        Return Math.Round(value, 6).ToString("F6", CultureInfo.InvariantCulture)
    End Function

    Private Sub IgnoreConstraint(action As Action)
        Try
            action()
        Catch ex As Exception
            WriteLog("  Зависимость пропущена: " & ex.Message)
        End Try
    End Sub

    Private Sub OptionalDisplay(label As String, action As Action)
        ' Как в Python: отказ оформления записать, но не отменять присадку.
        ' Этот обработчик не применяется к геометрии, размерам и отверстиям.
        Try
            action()
        Catch ex As Exception
            WriteLog("  Оформление пропущено (" & label & "): " & ex.Message)
        End Try
    End Sub

    Private Function Seconds(watch As Stopwatch) As String
        Return watch.Elapsed.TotalSeconds.ToString("F3", CultureInfo.InvariantCulture)
    End Function

    Private Sub LogStage(label As String, watch As Stopwatch)
        WriteLog(label & ": " & Seconds(watch) & "s")
        watch.Restart()
    End Sub

    Private Sub WriteLog(message As String)
        log.WriteLine(message)
        log.Flush()
    End Sub
End Class
