' Four confirmats on selected planar faces.
' Set the fixed offset from both ends; centers 1-2 and 4-3 are each 96 mm apart.
' Multiple coplanar faces share a sketch, following the 2-inch rule.
' Modules are included with AddVbFile and must not be run separately.
' Log: 02_confirmat_4inch_fixCentr_ilogic.log in project root.
AddReference "System.Drawing.dll"
AddReference "System.Windows.Forms.dll"
AddReference "Autodesk.Inventor.Interop.dll"
Imports Inventor
Imports System.Collections.Generic
Imports System.Diagnostics
Imports System.Globalization
Imports System.IO
Imports System.Text
Imports System.Text.RegularExpressions
Imports System.Windows.Forms

AddVbFile "Modules\ConfirmatContext.vb"
AddVbFile "Modules\ConfirmatConfig.vb"
AddVbFile "Modules\ConfirmatDialog.vb"
AddVbFile "Modules\ConfirmatSketches.vb"
AddVbFile "Modules\ConfirmatReference.vb"
AddVbFile "Modules\ConfirmatHoles.vb"

AddVbFile "Modules\ConfirmatWorkflow.vb"

Public Class ThisRule
    Public Sub Main()
        app = ThisApplication
        RunConfirmat(4)
    End Sub
End Class
