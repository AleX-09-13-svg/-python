' ТРИ СТЯЖКИ, ТОЧНЫЕ КРАЙНИЕ ОТСТУПЫ. Обычное внешнее правило для .ipt.
' Выбор тройками: 1–2) узкая грань и смежная пласть одного тела; 3) плоская грань со стороны отсчёта.
' Первые две грани сортируются по площади; третья служит только ориентиром и может быть на другом теле.
' Для нескольких комплектов повторяйте тройки. На ориентирующей грани отверстия не создаются.
' В окне — пользовательский параметр ТОЧНОГО отступа от края до крайней стяжки.
' Пролёт D = длина общего ребра − 2 × отступ. От крайней у третьей грани до средней:
' floor((D / 2) / 32 мм) × 32 мм. Средняя смещена к ориентиру, если половина пролёта не кратна 32 мм.
' Четыре шканта: два крайних и по одному в 32 мм с каждой стороны средней стяжки.
' На пласти — три чашки. До построения проверяются пересечения отверстий.
' Журнал: stiajka_3_ilogic.log в ProjectRoot. Modules отдельно не запускать.
AddReference "System.Drawing.dll"
AddReference "System.Windows.Forms.dll"
AddReference "Autodesk.Inventor.Interop.dll"
Imports Inventor
Imports System.Collections.Generic
Imports System.Diagnostics
Imports System.Globalization
Imports System.IO
Imports System.Text
Imports System.Text.RegularExpressions
Imports System.Windows.Forms

AddVbFile "Modules\StiajkaContext.vb"
AddVbFile "Modules\StiajkaConfig.vb"
AddVbFile "Modules\StiajkaSelection.vb"
AddVbFile "Modules\Stiajka_3_Selection.vb"
AddVbFile "Modules\StiajkaSketches.vb"
AddVbFile "Modules\StiajkaHoles.vb"
AddVbFile "Modules\Stiajka_3_Dialog.vb"
AddVbFile "Modules\Stiajka_3_Layout.vb"

Public Class ThisRule
    Private Const Prefix As String = "DrillingSketch_3pcs"
    Private Const TieCount As Integer = 3
    Private Const OffsetDialogTitle As String = "Три стяжки — фиксированный отступ"
    Private Const OffsetDialogLabel As String = "Пользовательский параметр точного отступа от края до центра крайней стяжки:"

    Public Sub Main()
        app = ThisApplication
        bodies.Clear()
        reserved.Clear()
        Dim logPath As String = System.IO.Path.Combine(ProjectRoot, "stiajka_3_ilogic.log")
        Dim transaction As Inventor.Transaction = Nothing
        Dim previousScreen As Boolean = app.ScreenUpdating
        Dim total As Stopwatch = Nothing
        Using writer As New StreamWriter(logPath, False, New UTF8Encoding(False))
            log = writer
            Try
                WriteLog("Стяжка 3 шт. iLogic Native. " & DateTime.Now.ToString("yyyy-MM-dd HH:mm:ss"))
                If app.ActiveDocument Is Nothing OrElse app.ActiveDocument.DocumentType <> DocumentTypeEnum.kPartDocumentObject Then
                    Throw New Exception("Откройте деталь .ipt и выберите три грани: две для присадки, третью для ориентации.")
                End If
                part = DirectCast(app.ActiveDocument, PartDocument)
                comp = part.ComponentDefinition
                tg = app.TransientGeometry
                factory = app.TransientObjects
                Dim phase As Stopwatch = Stopwatch.StartNew()
                Dim jobs As List(Of PairJob) = SelectedThreeFaceJobs()
                LoadConfig()
                LogStage("Грани, общее ребро и настройки", phase)
                Dim edgeParam As String = ChooseOffset()
                If String.IsNullOrEmpty(edgeParam) Then
                    WriteLog("Отменено пользователем.")
                    Return
                End If
                phase.Restart()
                Dim edgeUser As UserParameter = comp.Parameters.UserParameters.Item(edgeParam)
                Dim offsetParam As String = SettingParameter("offset", "Стяжка_отступ")
                Dim required As List(Of String) = RequiredParameters(edgeParam)
                For Each name As String In required
                    Try
                        Dim parameter As Inventor.Parameter = comp.Parameters.Item(name)
                    Catch
                        Throw New Exception("В детали отсутствует параметр: " & name)
                    End Try
                Next
                Dim offsetValue As Double = CDbl(comp.Parameters.Item(offsetParam).Value)
                Dim edgeValue As Double = CDbl(edgeUser.Value)
                WriteLog("Параметр точного отступа от края: " & edgeParam & "; " & Rounded(edgeValue * 10) & " мм")
                If offsetValue <= 0 OrElse edgeValue < 0 Then Throw New Exception("Проверьте положительный отступ стяжки и отступ от кромки.")
                For Each job As PairJob In jobs
                    Dim length As Double = job.Common.StartVertex.Point.DistanceTo(job.Common.StopVertex.Point)
                    ValidateLayout(length, edgeValue)
                    job.AnchorAtCommonStart = ReferenceAnchorAtStart(job, edgeValue)
                    Dim span As Double = PointSpan(length, edgeValue)
                    Dim pitch As Double = MiddlePitch(span)
                    WriteLog("База по третьей грани: " & If(job.AnchorAtCommonStart, "начало", "конец") & " общего ребра")
                    WriteLog("От крайней со стороны третьей грани до средней: " & Rounded(pitch * 10) &
                        " мм; от средней до другой крайней: " & Rounded((span - pitch) * 10) & " мм")
                Next
                LogStage("Проверка параметров и чтение значений", phase)
                transaction = app.TransactionManager.StartTransaction(part, "Три стяжки — iLogic Native")
                EnsureKeep(required)
                LogStage("Подготовка Keep_Excel_Params", phase)
                total = Stopwatch.StartNew()
                phase.Restart()
                app.ScreenUpdating = False
                BuildSketches(jobs, edgeParam, edgeValue, offsetParam, offsetValue, phase)
                ' До этого места отверстий нет: исходные ссылки на грани ещё действительны.
                For Each job As PairJob In jobs
                    job.Neighbor = FindNeighbor(job)
                Next
                LogStage("Поиск соседних тел", phase)
                BuildHoles(jobs)
                LogStage("Все отверстия", phase)
                part.Update()
                LogStage("Обновление документа", phase)
                transaction.End()
                transaction = Nothing
                app.ScreenUpdating = previousScreen
                total.Stop()
                WriteLog("05: Общее время построения: " & Seconds(total) & "s")
                WriteLog("05: Готово. Пар граней: " & jobs.Count.ToString())
                log.Flush()
            Catch ex As Exception
                WriteLog("ОШИБКА: " & ex.ToString())
                If transaction IsNot Nothing Then
                    Try
                        transaction.Abort()
                        WriteLog("Изменения этого запуска отменены.")
                    Catch rollback As Exception
                        WriteLog("Ошибка отмены: " & rollback.ToString())
                    End Try
                End If
                log.Flush()
                app.ScreenUpdating = previousScreen
                MessageBox.Show(ex.Message & vbCrLf & "Подробности: " & logPath, "Три стяжки — ошибка", MessageBoxButtons.OK, MessageBoxIcon.Error)
            Finally
                app.ScreenUpdating = previousScreen
            End Try
        End Using
    End Sub
End Class
